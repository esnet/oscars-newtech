module oscars {
    namespace "http://net.es/oscars";
    prefix oscars;

    import ietf-inet-types {
        prefix inet;
    }

    import tailf-ncs {
        prefix ncs;
    }

    import tailf-common {
        prefix tailf;
    }

    list oscars {

        uses ncs:service-data;
        ncs:servicepoint "oscars";

        key name;
        leaf name {
            type string;
        }

        leaf serviceId {
            mandatory true;
            type uint32 {
                range "6000..6999";
            }
        }

        leaf mtu {
            type uint32 {
                range "1500..9800";
            }
        }

        grouping endpoint {
            leaf ifce {
                mandatory true;
                type string;
            }
            leaf vlan-id {
                mandatory true;
                type uint32 {
                    range "2..4094";
                }
            }

        }

        list device {
            key "name";
            leaf name {
                tailf:info "Device";
                type leafref {
                    path "/ncs:devices/ncs:device/ncs:name";
                }
            }
            list fixture {
                uses endpoint;
                key "ifce vlan-id";
                leaf qos {
                    tailf:info "QoS policy id";
                    type leafref {
                        path "/qos/id";
                    }
                }
            }
            leaf aluLoopback {
                type inet:ip-address;
            }


            list sdp {
                key sdpId;
                leaf sdpId {
                    mandatory true;
                    type uint32 {
                        range "6000..6999";
                    }
                }
                leaf name {
                    mandatory true;
                    type string;
                }

                leaf vc-id {
                    mandatory true;
                    type uint32 {
                        range "6000..6999";
                    }
                }
                leaf type {
                    type enumeration {
                        enum primary;
                        enum protect;
                    }
                }
                leaf far-end {
                    mandatory true;
                    type inet:ip-address;
                }
                leaf neighbor {
                    type inet:ip-address;
                }
                leaf lsp {
                    mandatory true;
                    type leafref {
                        path "/oscars/device/lsp/name";
                    }
                }

            }

            list lsp {
                key name;
                leaf name {
                    type string;
                }

                leaf neighbor {
                    type inet:ip-address;
                }

                leaf to {
                    mandatory true;
                    type inet:ip-address;
                }

                leaf metric {
                    mandatory true;
                    type uint32 {
                        range "1..99999";
                    }
                }
                leaf holdPriority {
                    mandatory true;
                    type uint32 {
                        range "1..4096";
                    }
                }
                leaf setupPriority {
                    mandatory true;
                    type uint32 {
                        range "1..4096";
                    }
                }

                list hop {
                    leaf order {
                        mandatory true;
                        type uint32 {
                            range "1..4096";
                        }
                    }
                    key address;
                    leaf address {
                        mandatory true;
                        type inet:ip-address;
                    }
                }
            }


        }
    }

    list qos {
        key "id";
        leaf id {
            type string;
        }
        leaf excess-action {
            mandatory true;
            type enumeration {
                enum drop {
                    tailf:info "Drop";
                }
                enum scavenger {
                    tailf:info "Re-mark as scavenger";
                }
            }

        }
        leaf inMbps {
            mandatory true;
            type uint32 {
                range "0..100000";
            }
        }
        leaf egMbps {
            mandatory true;
            type uint32 {
                range "0..100000";
            }
        }
    }
}
